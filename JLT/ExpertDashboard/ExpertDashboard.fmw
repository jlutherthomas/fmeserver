FME workspace ExpertDashboard.fmw

Parameters:
- DestDataset_HTML = /Users/jlutherthomas/Desktop   # HTML Files(*.html)|*.html Destination Html File
- Expert = Jen   # Which Expert are you?
- SalesforceURL = https://safe.my.salesforce.com   # Enter URL for Staging or Production
- SFClientKey = 3MVG99OxTyEMCQ3iglRtaxxNBn6hAwsDc7T8fscHq7oz9X0wJvTm3Y6.BiszNPKOx.BjyiWZ7YZB_WfYCqzfs   # ClientKey
- SFClientSecret =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   # Client Secret
- SFRefreshToken = 5Aep8619juAXTkx27bjlWqR3KGPsBpWgeSctjD3O7z2CzkzGRW1EbJBzz34.CvSO4ekfedC0o9Uq6aKcoXeTUUw

Writers:
- HTML_1: HTML to $(DestDataset_HTML)

AttributeCreator_6
    ATTR_TABLE = SET_TO Order = 1
    -> FeatureHolder
AttributeCreator_7
    ATTR_TABLE = SET_TO Order = 4
    -> FeatureHolder
AttributeCreator_8
    ATTR_TABLE = SET_TO Order = 2
    -> FeatureHolder
AttributeCreator_5
    ATTR_TABLE = SET_TO Order = 5
    -> FeatureHolder
FeatureHolder
    -> Sorter_4
Sorter_4
    SORT_PARM = Order NUMERIC ASCENDING
    SORTED -> HTML (writer HTML_1)
HTML (writer HTML_1)
    attributes: html_content buffer
SalesforceConnector
    OPERATION_TYPE = SOQL Query

Bookmark: Community
Creator_2
    GEOMTYPE = Geometry Object
    NUM = 1
    CREATED -> HTTPCaller
HTTPCaller
    ADDITIONAL_URL_PARAMETERS = page;@Value(page) pageSize;300
    AUTH_METHOD = Basic
    AUTH_PASSWORD =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
    AUTH_USERNAME = jlutherthomas
    CONNECTION_TIMEOUT_LENGTH = 60
    CUSTOM_HEADERS = Accept;application/json Content-type;application/json
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = auto-detect
    TARGET_URL = https://knowledge.safe.com/services/v2/question.json
    TRANSFER_TIMEOUT_LENGTH = 90
    USE_COOKIES = No
    VERIFY_SSL_CERTIFICATES = Yes
    -> JSONFragmenter_3
JSONFragmenter_3
    EXPLODE_FORMAT = JSON
    EXTRACT_ATTR = Yes
    JSON_ATTR = _response_body
    JSON_QUERY = json["list"][*]
    RECURSIVE = Yes
    FRAGMENTS -> JSONFlattener
JSONFlattener
    ERROR_LIST_ATTR = _json_error
    JSON_DOCUMENT = @Value(_response_body)
    NEW_ATTRIBUTES = id title creationDate title childrenIds commentIds creationDateFormatted author.username author.id answerCount slug viewCount childrenIds{} title
    RECURSIVE = Yes
    -> TestFilter
TestFilter
    DEFAULT_VALUE = NoBestAnswer
    TEST_LIST = BOOL_OP,OR,COMPOSITE_TEST,<Unused>,TEST_CLAUSE,"TEST @Value(answerCount) = 0",No answers,BOOL_OP,OR,COMPOSITE_TEST,<Unused>,TEST_CLAUSE,"TEST @Value(_response_body) CONTAINS "nodeStates":["accepted"]",BestAnswer
    No answers -> DuplicateFilter
    NoBestAnswer -> DuplicateFilter
DuplicateFilter
    INPUT_ORDERED_CHOICE = No
    KEYATTR = slug
    UNIQUE -> Sorter_2
Sorter_2
    SORT_PARM = id NUMERIC DESCENDING
    SORTED -> Sampler_3
Sampler_3
    RATE = 5
    SAMPLE_MODE = No
    SAMPLE_TYPE_LONG = First N Features
    SAMPLED -> Sampler_4
Sampler_4
    RATE = 1
    SAMPLE_MODE = No
    SAMPLE_TYPE_LONG = First N Features
    SAMPLED -> AttributeCreator_4
    NOT_SAMPLED -> AttributeCreator_4
AttributeCreator_4
    ATTR_TABLE:
      SET_TO pageUrl = https://knowledge.safe.com/questions/@Value(id)/@Value(slug).html
      SET_TO QAQuestions = <a href="@Value(pageUrl)">@Value(title)</a>
    -> HTMLReportGenerator_3
HTMLReportGenerator_3
    CONTENT_LIST = HEADER LIST
    PAGE_CONFIG = HEADER{{TEXT;Unanswered Community Questions;HEADER;H2;ALIGNMENT;LEFT;COLOR;0,0,0;FME_CONTROLLER_QUERY_FILE;transformers/dependencies/html5/Header.fme}}LIST{{ATTR;QAQuestions;STYLE;NONE;COLOR;0,0,0;BADGE;;FME_CONTROLLER_QUERY_FILE;transformers/dependencies/html5/List.fme}}
    TITLE = Community Questions to check
    -> StringPairReplacer_3
StringPairReplacer_3
    CASE = no
    MAP = &lt; < &gt; >
    RESULT_ATTR = html_content
    SRC_ATTR = html_content
    -> HTMLLayouter
HTMLLayouter
    COLUMN = 1
    DIV_STYLE = VERTICAL
    LAYOUT = GRID
    ROW = 2
    -> AttributeCreator_10
AttributeCreator_10
    ATTR_TABLE = SET_TO Order = 3
    -> FeatureHolder

Bookmark: Bugzilla
Creator
    GEOMTYPE = Geometry Object
    NUM = 1
    CREATED -> SQLExecutor [INITIATOR]
SQLExecutor
    COMBINE_ATTRS = Result Attributes Only
    COMBINE_GEOM = Initiator Geometry Only
    DATASET = CBAR
    EXPOSED_ATTRIBUTE_LIST = bug_id,qa_first,qa_last,assigned_last,assigned_first,cases,cf_ci,qa_team,bug_status,short_desc,resolution
    FORMAT = MYSQL_AURORA_SPATIAL
    MYSQL_AURORA_SPATIAL_HOST = bar-rds.safe.internal
    MYSQL_AURORA_SPATIAL_PASSWORD =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
    MYSQL_AURORA_SPATIAL_PORT = 3306
    MYSQL_AURORA_SPATIAL_QUERY_FEATURE_TYPES_FOR_MERGE_FILTERS = Yes
    MYSQL_AURORA_SPATIAL_USER_NAME = barread
    SQL_STATEMENT:
      SELECT * from CBAR.statzilla_all_bugs
      WHERE qa_team LIKE 'Tech Experts'
      AND (bug_status LIKE 'VERIFIED' OR resolution LIKE 'NEEDSINFO')
    RESULT -> Tester_3
Tester_3
    BOOL_OP = OR
    TEST_CLAUSE = TEST @Value(qa_first) BEGINS_WITH $(Expert)
    PASSED -> AttributeManager_3
AttributeManager_3
    ATTR_TABLE = SET_TO bugurl = <a href="http://bugzilla/show_bug.cgi?id=@Value(bug_id)">@Value(bug_id)</a>
    -> HTMLReportGenerator_2
HTMLReportGenerator_2
    CONTENT_LIST = HEADER TABLE
    PAGE_CONFIG = HEADER{{TEXT;PRs needing attention;HEADER;H2;ALIGNMENT;LEFT;COLOR;0,0,0;FME_CONTROLLER_QUERY_FILE;transformers/dependencies/html5/Header.fme}}TABLE{{STYLE;DEFAULT;TABLE;bugurl|BugID/short_desc|Title/bug_status|Status/resolution|Resolution;TABLE_GROUP;;FME_CONTROLLER_QUERY_FILE;transformers/dependencies/html5/Table.fme}}
    TITLE = Experts Dashboard
    -> StringPairReplacer_2
StringPairReplacer_2
    CASE = no
    MAP = &lt; < &gt; >
    RESULT_ATTR = html_content
    SRC_ATTR = html_content
    -> HTMLLayouter_5
HTMLLayouter_5
    COLUMN = 1
    DIV_STYLE = VERTICAL
    LAYOUT = GRID
    ROW = 6
    TITLE = PRs that need attention
    -> AttributeCreator_9
AttributeCreator_9
    ATTR_TABLE = SET_TO Order = 6
    -> FeatureHolder

Bookmark: Queued Cases
Creator_SF
    GEOMTYPE = Geometry Object
    NUM = 1
    CREATED -> Get_AccessToken
Get_AccessToken: HTTPCaller
    ADDITIONAL_URL_PARAMETERS = grant_type;refresh_token refresh_token;$(SFRefreshToken) client_id;$(SFClientKey) client_secret;$(SFClientSecret)
    CONNECTION_TIMEOUT_LENGTH = 60
    CUSTOM_HEADERS = Accept;application/json
    ERROR_ATTR = _error
    FOLLOW_REDIRECTS = Yes
    HTTP_METHOD = POST
    RESPONSE_HEADER_LIST_ATTR = _headers
    SAVE_FILE = Attribute
    STATUS_CODE_ATTR = _http_status_code
    TARGET_ATTR = _bearer_token
    TARGET_ATTR_ENCODING = auto-detect
    TARGET_URL = $(SalesforceURL)/services/oauth2/token
    TRANSFER_TIMEOUT_LENGTH = 90
    UPLOAD_CONTENT_TYPE = Text (text/plain)
    UPLOAD_TYPE = Specify Upload Body
    USE_COOKIES = No
    VERIFY_SSL_CERTIFICATES = Yes
    -> JSONFrag_GetToken
JSONFrag_GetToken: JSONFragmenter
    EXTRACT_ATTR = No
    JSON_DOCUMENT = @Value(_bearer_token)
    JSON_QUERY = json["access_token"]
    OUTPUT_ATTRIBUTE = sf_access_token
    EXPLODED -> HTTP_Report
    EXPLODED -> HTTP_Report_OpenCases
HTTP_Report: HTTPCaller
    ADDITIONAL_URL_PARAMETERS = includeDetails;true
    CONNECTION_TIMEOUT_LENGTH = 60
    CUSTOM_HEADERS = Authorization;Bearer @Value(sf_access_token)
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_report
    TARGET_ATTR_ENCODING = auto-detect
    TARGET_URL = $(SalesforceURL)/services/data/v34.0/analytics/reports/00O0c000009OpFU
    TRANSFER_TIMEOUT_LENGTH = 90
    USE_COOKIES = No
    VERIFY_SSL_CERTIFICATES = Yes
    -> JSONFormatter
JSONFormatter
    ERROR_LIST_ATTR = _json_error
    FORMAT = Pretty Print
    INDENT_STYLE = 3 spaces
    JSON_DOCUMENT = @Value(_response_report)
    OUTPUT_ATTR = _formatted
    OUTPUT_ENCODING = UTF-8
    REMOVE_EMPTY_OBJECTS_AND_ARRAYS = No
    REMOVE_EMPTY_STRINGS = No
    REMOVE_NULLS = No
    -> JSONFragmenter
JSONFragmenter
    EXPLODE_FORMAT = JSON
    EXTRACT_ATTR = Yes
    JSON_ATTR = _formatted
    JSON_QUERY = json["factMap"]["T!T"]["rows"][*]
    NEW_ATTRIBUTES = dataCells{}.label
    RECURSIVE = Yes
    FRAGMENTS -> AttributeCreator
AttributeCreator
    ATTR_TABLE:
      SET_TO caseURL = https://safe.my.salesforce.com/@Value(dataCells{2}.label)
      SET_TO case = @Value(dataCells{1}.label)
      SET_TO priority = @Value(dataCells{3}.label)
      SET_TO title = @Value(dataCells{6}.label)
      SET_TO slackMessage = *@Value(case)* @Value(title)
        @Value(caseURL)
      SET_TO CaseHyperlink = <a href="@Value(caseURL)">@Value(title)</a>
    -> Tester
Tester
    BOOL_OP = OR
    TEST_CLAUSE = TEST @Value(priority) >= 30
    PASSED -> StatisticsCalculator
    FAILED -> Sorter
Sorter
    SORT_PARM = priority NUMERIC DESCENDING
    SORTED -> Sampler_2
Sampler_2
    RATE = 1
    SAMPLE_MODE = No
    SAMPLE_TYPE_LONG = Every Nth Feature
    SAMPLED -> HTMLReportGenerator_6
StatisticsCalculator
    COMPUTE_HISTOGRAM = NO
    COUNT_ATTR = _count
    PREPEND_ATTR_NAME_CHOICE = For multiple results only
    STATS_ATTRS = case
    COMPLETE -> NoFeaturesTester
NoFeaturesTester
    NOINPUT -> AttributeCreator_3
    -> AttributeCreator_2
AttributeCreator_3
    ATTR_TABLE = SET_TO High Priority Summary = There are no High Priority cases
    -> Sorter_3
AttributeCreator_2
    ATTR_TABLE = SET_TO High Priority Summary = There are @Value(_count) High Priority cases:
    -> Sorter_3
Sorter_3
    SORT_PARM = priority NUMERIC DESCENDING
    SORTED -> HTMLReportGenerator
HTMLReportGenerator
    CONTENT_LIST = HEADER LIST
    PAGE_CONFIG = HEADER{{TEXT;@Value(High Priority Summary);HEADER;H2;ALIGNMENT;LEFT;COLOR;0,0,0;FME_CONTROLLER_QUERY_FILE;transformers/dependencies/html5/Header.fme}}LIST{{ATTR;CaseHyperlink;STYLE;NONE;COLOR;0,0,0;BADGE;;FME_CONTROLLER_QUERY_FILE;transformers/dependencies/html5/List.fme}}
    TITLE = High Priority Cases
    -> StringPairReplacer
StringPairReplacer
    CASE = no
    MAP = &lt; < &gt; >
    RESULT_ATTR = html_content
    SRC_ATTR = html_content
    -> HTMLLayouter_4
HTMLLayouter_4
    COLUMN = 1
    DIV_STYLE = VERTICAL
    LAYOUT = GRID
    ROW = 2
    TITLE = Cases in the queue
    -> AttributeCreator_8

Bookmark: Open Cases per agent
HTTP_Report_OpenCases: HTTPCaller
    ADDITIONAL_URL_PARAMETERS = includeDetails;true
    CONNECTION_TIMEOUT_LENGTH = 60
    CUSTOM_HEADERS = Authorization;Bearer @Value(sf_access_token)
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_report
    TARGET_ATTR_ENCODING = auto-detect
    TARGET_URL = $(SalesforceURL)/services/data/v34.0/analytics/reports/00O0c000009HquD
    TRANSFER_TIMEOUT_LENGTH = 90
    USE_COOKIES = No
    VERIFY_SSL_CERTIFICATES = Yes
    -> JSONFormatter_2
JSONFormatter_2
    ERROR_LIST_ATTR = _json_error
    FORMAT = Pretty Print
    INDENT_STYLE = 3 spaces
    JSON_DOCUMENT = @Value(_response_report)
    OUTPUT_ATTR = _formatted
    OUTPUT_ENCODING = UTF-8
    REMOVE_EMPTY_OBJECTS_AND_ARRAYS = No
    REMOVE_EMPTY_STRINGS = No
    REMOVE_NULLS = No
    -> JSONFragmenter_2
JSONFragmenter_2
    EXPLODE_FORMAT = JSON
    EXTRACT_ATTR = Yes
    JSON_ATTR = _formatted
    JSON_QUERY = json["factMap"]["T!T"]["rows"][*]
    NEW_ATTRIBUTES = dataCells{}.label dataCells{}.value
    RECURSIVE = Yes
    FRAGMENTS -> AttributeManager
AttributeManager
    ATTR_TABLE:
      SET_TO caseOwner = @Value(dataCells{0}.label)
      SET_TO caseID = @Value(dataCells{1}.value)
      SET_TO caseTitle = @Value(dataCells{1}.label)
      SET_TO caseURL = https://safe.my.salesforce.com/@Value(dataCells{1}.value)
    -> Tester_2
Tester_2
    BOOL_OP = OR
    TEST_CLAUSE = TEST @Value(caseOwner) BEGINS_WITH $(Expert)
    PASSED -> AttributeManager_2
AttributeManager_2
    ATTR_TABLE = SET_TO CaseTitle = <a href="@Value(caseURL)">@Value(caseTitle)</a>
    -> HTMLReportGenerator_4
HTMLReportGenerator_4
    CONTENT_LIST = HEADER SEPARATOR HEADER TABLE
    PAGE_CONFIG = HEADER{{TEXT;$(Expert)'s FME Expert Dashbaord;HEADER;H1;ALIGNMENT;CENTER;COLOR;0,0,0;FME_CONTROLLER_QUERY_FILE;transformers/dependencies/html5/Header.fme}}SEPARATOR{{WIDTH;1;FME_CONTROLLER_QUERY_FILE;transformers/dependencies/html5/Separator.fme}}HEADER{{TEXT;My Open Cases;HEADER;H2;ALIGNMENT;LEFT;COLOR;0,0,0;FME_CONTROLLER_QUERY_FILE;transformers/dependencies/html5/Header.fme}}TABLE{{STYLE;DEFAULT;TABLE;caseOwner|Case Owner/CaseTitle|Case Subject;TABLE_GROUP;;FME_CONTROLLER_QUERY_FILE;transformers/dependencies/html5/Table.fme}}
    TITLE = Experts Dashboard
    -> HTMLLayouter_2
HTMLLayouter_2
    COLUMN = 1
    DIV_STYLE = VERTICAL
    LAYOUT = GRID
    ROW = 1
    TITLE = Your open cases
    -> StringPairReplacer_4
StringPairReplacer_4
    CASE = no
    MAP = &lt; < &gt; >
    RESULT_ATTR = html_content
    SRC_ATTR = html_content
    -> AttributeCreator_6

Bookmark: All Cases
HTMLReportGenerator_6
    CONTENT_LIST = HEADER TABLE
    PAGE_CONFIG = HEADER{{TEXT;All Cases;HEADER;H2;ALIGNMENT;LEFT;COLOR;0,0,0;FME_CONTROLLER_QUERY_FILE;transformers/dependencies/html5/Header.fme}}TABLE{{STYLE;DEFAULT;TABLE;priority|Priority/CaseHyperlink|Case Subject;TABLE_GROUP;;FME_CONTROLLER_QUERY_FILE;transformers/dependencies/html5/Table.fme}}
    TITLE = Experts Dashboard
    -> StringPairReplacer_5
StringPairReplacer_5
    CASE = no
    MAP = &lt; < &gt; >
    RESULT_ATTR = html_content
    SRC_ATTR = html_content
    -> HTMLLayouter_6
HTMLLayouter_6
    COLUMN = 1
    DIV_STYLE = VERTICAL
    LAYOUT = GRID
    ROW = 4
    TITLE = Cases in the queue
    -> AttributeCreator_7

Bookmark: Calendar
Creator_3
    GEOMTYPE = Geometry Object
    NUM = 1
    CREATED -> HTMLReportGenerator_5
HTMLReportGenerator_5
    CONTENT_LIST = HEADER HTML
    PAGE_CONFIG = HEADER{{TEXT;Tech Experts Availability;HEADER;H2;ALIGNMENT;LEFT;COLOR;0,0,0;FME_CONTROLLER_QUERY_FILE;transformers/dependencies/html5/Header.fme}}HTML{{HTML;<iframe src="https://calendar.google.com/calendar/embed?showNav=0&amp;showDate=0&amp;showPrint=0&amp;showTabs=0&amp;showCalendars=0&amp;showTz=0&amp;mode=WEEK&amp;height=600&amp;wkst=2&amp;bgcolor=%23FFFFFF&amp;src=safe.com_nhu2op6tnvijbj3r4inrobq2ro%40group.calendar.google.com&amp;color=%23AB8B00&amp;ctz=America%2FVancouver" style="border-width:0" width="800" height="600" frameborder="0" scrolling="no"></iframe>;FME_CONTROLLER_QUERY_FILE;transformers/dependencies/html5/Custom HTML.fme}}
    TITLE = Experts Dashboard
    -> HTMLLayouter_3
HTMLLayouter_3
    COLUMN = 1
    DIV_STYLE = VERTICAL
    LAYOUT = GRID
    ROW = 5
    -> AttributeCreator_5

FME custom transformer NoFeaturesTester
This transformer checks whether there are any input features. If not, then a single feature is ouput via the NOINPUT port. If INPUT features exist, then they are output via the INPUT output port.
Other transformers often generate features that signify an error condition. This transformer can be used to check for those features and if those features exists, then a separate action can be triggered.
    Example
This may be useful to test if any data emerges from a reader, when the 'Ignore Failed Readers' advanced parameter is set to yes.
Input Ports
    Input
Features to be checked for existence
    Output Ports
    NoInput
If no Input features exist, a single featue is returned via the NoInput port
    Output
Any feature that entered the Input port is returned via the Output port

INPUT (input)
    -> Sampler
    -> OUTPUT (output)
OUTPUT (output)
Sampler
    RATE = 1
    SAMPLE_MODE = No
    SAMPLE_TYPE_LONG = First N Features
    SAMPLED -> AttributeCreator_2
AttributeCreator_2
    ATTR_TABLE:
      SET_TO count = 0
      SET_TO remove = yes
    -> DuplicateFilter
Creator
    GEOMTYPE = Geometry Object
    NUM = 1
    CREATED -> AttributeCreator_3
AttributeCreator_3
    ATTR_TABLE = SET_TO no_features = true
    -> DuplicateFilter
DuplicateFilter
    INPUT_ORDERED_CHOICE = No
    KEYATTR = count
    UNIQUE -> Tester
Tester
    BOOL_OP = OR
    TEST_CLAUSE = TEST @Value(remove) != yes
    PASSED -> AttributeRemover
AttributeRemover
    REMOVE_ATTRS = count,remove
    -> NOINPUT (output)
NOINPUT (output)
